(defun c:AIPLAN (/)

  ;; ------------------------------------------------------------
  ;; AI TOWN PLANNING - APS AUTOCAD TEST
  ;; ------------------------------------------------------------

  (setvar "CMDECHO" 0)

  ;; Layers
  (command "-LAYER" "M" "A-SITE" "")
  (command "-LAYER" "M" "A-SETBACK" "")
  (command "-LAYER" "M" "A-WALL" "")
  (command "-LAYER" "M" "A-DOOR" "")
  (command "-LAYER" "M" "A-TEXT" "")
  (command "-LAYER" "M" "A-DIM" "")

  ;; ------------------------------------------------------------
  ;; SITE
  ;; 24m x 32m
  ;; ------------------------------------------------------------

  (setvar "CLAYER" "A-SITE")

  (command
    "_.RECTANG"
    '(0 0)
    '(24 32)
  )

  ;; ------------------------------------------------------------
  ;; BUILDABLE AREA
  ;; 3m side/rear, 6m front
  ;; ------------------------------------------------------------

  (setvar "CLAYER" "A-SETBACK")

  (command
    "_.RECTANG"
    '(3 6)
    '(21 29)
  )

  ;; ------------------------------------------------------------
  ;; BUILDING
  ;; ------------------------------------------------------------

  (setvar "CLAYER" "A-WALL")

  (command
    "_.RECTANG"
    '(3 6)
    '(21 26)
  )

  ;; ------------------------------------------------------------
  ;; INTERNAL WALLS
  ;; ------------------------------------------------------------

  ;; Vertical division
  (command
    "_.LINE"
    '(12 6)
    '(12 26)
    ""
  )

  ;; Horizontal divisions
  (command
    "_.LINE"
    '(3 15)
    '(21 15)
    ""
  )

  (command
    "_.LINE"
    '(3 21)
    '(12 21)
    ""
  )

  (command
    "_.LINE"
    '(12 19)
    '(21 19)
    ""
  )

  ;; ------------------------------------------------------------
  ;; TEXT
  ;; ------------------------------------------------------------

  (setvar "CLAYER" "A-TEXT")

  (command
    "_.TEXT"
    '(6 11)
    "0.6"
    "0"
    "LIVING / DINING"
  )

  (command
    "_.TEXT"
    '(14 11)
    "0.6"
    "0"
    "KITCHEN"
  )

  (command
    "_.TEXT"
    '(6 23)
    "0.6"
    "0"
    "MASTER BEDROOM"
  )

  (command
    "_.TEXT"
    '(14 22)
    "0.6"
    "0"
    "BEDROOM 2"
  )

  (command
    "_.TEXT"
    '(14 17)
    "0.5"
    "0"
    "COMMON WC"
  )

  (command
    "_.TEXT"
    '(6 17)
    "0.5"
    "0"
    "ATTACHED WC"
  )

  ;; ------------------------------------------------------------
  ;; TITLE
  ;; ------------------------------------------------------------

  (command
    "_.TEXT"
    '(3 3)
    "0.8"
    "0"
    "AI TOWN PLANNING - APS AUTOCAD TEST"
  )

  ;; ------------------------------------------------------------
  ;; DIMENSIONS
  ;; ------------------------------------------------------------

  (setvar "CLAYER" "A-DIM")

  (command
    "_.DIMLINEAR"
    '(0 0)
    '(24 0)
    '(12 -2)
  )

  (command
    "_.DIMLINEAR"
    '(24 0)
    '(24 32)
    '(27 16)
  )

  ;; ------------------------------------------------------------
  ;; SAVE
  ;; ------------------------------------------------------------

  (command "_.ZOOM" "_E")

  (command "_.QSAVE")

  (setvar "CMDECHO" 1)

  (princ)
)
(princ)
